# 系统需求
创建者：末泽

# Specification: 需求表单文档
- 描述: 需求表单

## SRF-1
- 描述: 在起飞降落及停靠过程中，起落架系统应该为整机提供支撑
- 需求条目: 起飞降落支持

## SRF-2
- 需求条目: 收放
- 描述: 起落架系统应该具备起落架与舱门的收放功能

### SRF-2.1
- 需求条目: 读取收放信号
- 描述: 起落架系统应该能够对飞控系统发出的信号进行读取

### SRF-2.2
- 需求条目: 自动收放
- 描述: 起落架系统应该具备起落架及舱门的自主收放能力

### SRF-2.3
- 需求条目: 应急放下
- 描述: 在出现故障时，起落架系统应该能进行应急放下

### SRF-2.4
- 需求条目: 位置检测
- 描述: 起落架系统应该具备监测起落架和舱门是否收放/开关到位的功能

## SRF-3
- 需求条目: 故障监测及报警
- 描述: 起落架系统应该具备系统故障监测及报警功能

## SRF-4
- 需求条目: 状态反馈
- 描述: 起落架系统应该能够向飞控系统反馈目前状态

## SRF-5
- 需求条目: 减震吸收
- 描述: 在飞行器着陆时，起落架系统应该能够吸收着陆时产生的冲击力，减少对飞机结构的应力

## SRF-6
- 需求条目: 自锁能力
- 描述: 起落架系统应该具备自锁能力

## SRF-7
- 需求条目: 刹车
- 描述: 在飞行器接近地面时，起落架系统应该具备刹车功能

### SRF-7.1
- 需求条目: 读取刹车信号
- 描述: 起落架系统应该能够读取飞控系统发出的刹车信号

### SRF-7.2
- 需求条目: 自动刹车
- 描述: 起落架系统应该能够进行自动刹车

### SRF-7.3
- 需求条目: 人工刹车
- 描述: 在自动刹车系统不可用或在某些特殊情况下需进行精细控制，起落架系统应该能够进行人工刹车

### SRF-7.4
- 需求条目: 停留刹车
- 描述: 当飞行器在地面上长时间停留时，起落架系统应该能锁定飞机

## SRF-8
- 需求条目: 转向
- 描述: 在跑道上滑行时，起落架系统应该能够进行转向操作

### SRF-8.1
- 需求条目: 读取转向信号
- 描述: 起落架系统应该能够读取飞控系统发出的转弯信号

## SRP-1
- 描述: 起落架系统平均故障间隔时间应该不低于1000h
- 需求条目: 低故障率

## SRP-2
- 描述: 起落架总重应该不超过整机的10%
- 需求条目: 重量要求

## SRP-3
- 描述: 起落架收放作动筒载荷不超过2MPa
- 需求条目: 收放需求

## SRP-4
- 描述: 起落架系统应该具备耐高温低温、耐腐蚀、地形适应的能力
- 需求条目: 环境适应性

### SRP-4.1
- 描述: 起落架系统应该防水、适应极端气温。
- 需求条目: 气候适应

### SRP-4.2
- 描述: 起落架系统应该能够抵抗盐雾、化学物质等环境因素的侵蚀。
- 需求条目: 耐腐蚀性

### SRP-4.3
- 描述: 在非常规跑道上工作时，起落架系统应该能正常运行。
- 需求条目: 地形适应性

## SRP-2
- 描述: 起落架材料应该高强度、耐腐蚀、环保、轻量
- 需求条目: 材料要求
