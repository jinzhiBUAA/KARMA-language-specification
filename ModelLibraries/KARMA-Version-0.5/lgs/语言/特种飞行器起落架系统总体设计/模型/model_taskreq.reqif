# 任务需求
创建者：末泽

# Specification: 需求表单文档
- 描述: 需求表单

## STN-1
- 描述: 在工作过程中，起落架系统应该安全可靠。
- 需求条目: 运行安全

## STN-2
- 描述: 起落架系统应该具备刹车功能。
- 需求条目: 刹车

## STN-3
- 描述: 起落架系统应该具备收放功能。
- 需求条目: 收放

## STN-4
- 描述: 起落架系统应该具备转向功能。
- 需求条目: 转向

## STN-5
- 描述: 起落架系统应该具备支撑整机重量的功能。
- 需求条目: 支撑

## STN-6
- 描述: 起落架系统应该具备吸收着陆时产生的冲击力，减少对飞机结构的应力的功能。
- 需求条目: 减震吸收
