# 利益相关者需求
创建者：末泽

# Specification: 需求表单文档
- 描述: 需求表单

## SN-1 (需求类型)
- 描述: 起落架系统应该存在安全保障。
- 需求条目: 安全性

### SN-1.1 (需求类型)
- 需求条目: 系统运行安全
- 描述: 起落架应该能正常进行起飞、降落、转向等操作。

### SN-1.2 (需求类型)
- 需求条目: 手动控制
- 描述: 如果自动刹车、收放功能失灵，驾驶员应该能手动操作完成相关功能。

### SN-1.3 (需求类型)
- 需求条目: 位置检测与预警
- 描述: 起落架系统应该具备位置检测与预警系统。

## SN-2 (需求类型)
- 需求条目: 可靠性
- 描述: 在规定的使用寿命内，起落架系统应该无需频繁维修。

### SN-2.1 (需求类型)
- 需求条目: 低故障率
- 描述: 起落架系统平均故障间隔时间应该不低于1000h。

## SN-3 (需求类型)
- 描述: 起落架系统应该能适应各种极端环境。
- 需求条目: 环境适应性

### SN-3.1 (需求类型)
- 描述: 起落架系统应该防水、适应极端气温。
- 需求条目: 气候适应

### SN-3.2 (需求类型)
- 描述: 起落架系统应该能够抵抗盐雾、化学物质等环境因素的侵蚀。
- 需求条目: 耐腐蚀性

### SN-3.3 (需求类型)
- 描述: 在非常规跑道上工作时，起落架系统应该能正常运行。
- 需求条目: 地形适应性

## SN-4 (需求类型)
- 需求条目: 参数要求
- 描述: 起落架相关参数应该满足相关标准。

### SN-4.1 (需求类型)
- 描述: 起落架材料应该高强度、耐腐蚀、环保、轻量。
- 需求条目: 材料要求

### SN-4.3 (需求类型)
- 需求条目: 重量要求
- 描述: 起落架总重应该不超过整机的10%。

### SN-4.4 (需求类型)
- 需求条目: 收放性能需求
- 描述: 起落架收放作动筒载荷不超过2MPa。

## SN-2.2 (需求类型)
- 需求条目: 便于维护
- 描述: 起落架系统维护时间和成本应该较低。

## R11

## SN-4.2 (需求类型)
- 需求条目: 尺寸要求
- 描述: 起落架尺寸应该符合相关标准。
