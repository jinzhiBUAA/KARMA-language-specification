# 0_1_使命分解
创建者：26453

# Specification: 需求表单文档
- 描述: 需求表单

## R1
- 使命: 设计制造毅力号

### R2
- 使命: 设计毅力号
- 主要客户: NASA
- 业务目标: 1.依据火星探索使命规划给出毅力号设计方案
- 运行任务: O.1.1设计毅力号

### R4
- 使命: 制造生产毅力号
- 主要客户: NASA
- 业务目标: 2.依据设计书完成生产制造
- 运行任务: O.1.3制造毅力号

### R5
- 使命: 火星车实验测试
- 主要客户: NASA
- 业务目标: 3.在地面实验室模拟火星车全部工作环境，确保能够在太空和火星完成工作
- 运行任务: O.1.4测试毅力号

## R3
- 使命: 运送火星车至火星

### R7
- 使命: 确保火星车成功发射
- 主要客户: 肯尼迪航天中心
- 业务目标: 4.保证火星车发射成功
- 运行任务: O.1.2准备运载火箭

#### R15
- 运行任务: O.2.1装载毅力号和航天器进入太空

### R8
- 使命: 将火星车运往火星
- 主要客户: 空气动力实验室、JPL实验室
- 业务目标: 5.监测维护航天器和火星车在太空运行状态直至火星
- 运行任务: O.2.2脱离火箭搭载毅力号进入巡航阶段

#### R16
- 运行任务: O.2.3太空运行监测与调整

### R9
- 使命: 火星车降落
- 主要客户: 空气动力实验室、JPL实验室
- 业务目标: 6.指挥火星车降落，采集降落过程中的数据
- 运行任务: 1_4_3_登陆阶段运行任务分配

## R6
- 使命: 火星探索

### R11
- 使命: 地质探索
- 主要客户: 科学探索团队、JPL实验室
- 业务目标: 7.通过火星车研究火星地表岩层、矿物质、研究对应地区的空气状况、气候、环境变化历史。
- 运行任务: O.4.14地质环境分析

### R12
- 使命: 天体生物学探索
- 主要客户: 科学探索团队、JPL实验室
- 业务目标: 8.确定研究地区是否能满足生命生存或存在过生命存在遗迹
- 运行任务: O.4.15生命迹象分析

### R13
- 使命: 样本采集储存
- 主要客户: 科学探索团队、JPL实验室
- 业务目标: 9.采集分析样本，并将样本保存在标记位置，以便未来可能的取回
- 运行任务: O.4.16样本采集

### R14
- 使命: 为未来探索做准备
- 主要客户: 美国政府、科学探索团队
- 业务目标: 10.进行飞行与制氧试验，为未来探测计划提供参考
- 运行任务: O.4.18制氧实验

#### R17
- 运行任务: O.4.2飞行测试

## R10
