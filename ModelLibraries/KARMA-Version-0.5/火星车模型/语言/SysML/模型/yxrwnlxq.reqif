# 1_4_4运行任务能力需求
创建者：26453

# Specification: 需求表单文档
- 描述: 需求表单

## R1
- 描述: 从这里开始编辑。
- 运行任务: O.1.5搭载毅力号准备发射
- 能力需求: 火星和太空工作能力

### R2
- 运行任务: O.2.1装载毅力号和航天器进入太空

## R3
- 运行任务: O.2.3太空运行监测与调整
- 能力需求: 通信能力

### R11
- 运行任务: O.4.5发送采集数据

## R4
- 能力需求: 远程控制能力
- 运行任务: O.4.10设置毅力号前进路线

### R12
- 运行任务: O.4.1控制监测毅力号实施探索任务

## R5
- 能力需求: 自主控制能力
- 运行任务: O.4.7分析、记录探索结果

## R6
- 能力需求: 导航能力
- 运行任务: O.4.6到达探索区域

## R7
- 能力需求: 姿态与高度感知能力
- 运行任务: O.3.1确认着陆点

### R9
- 运行任务: O.3.3状态监测，调整进入大气层中的下降姿态

### R10
- 运行任务: O.3.5打开降落伞

## R8
- 能力需求: 实验分析能力
- 运行任务: O.4.14地质环境分析

### R13
- 运行任务: O.4.18制氧实验
