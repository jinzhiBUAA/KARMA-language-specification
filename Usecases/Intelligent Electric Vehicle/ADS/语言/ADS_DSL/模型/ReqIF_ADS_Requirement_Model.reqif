# ADS需求模型
创建者：18756

# Specification: 需求表单文档
- 描述: 自动驾驶系统需求模型

## R1
- 需求描述: 当车辆处于没有人工干预状态时，ADS应该支持车辆自动完成各种驾驶任务。
- 需求ID: ADS-REQ-1
- 需求名称: 自动驾驶系统需求

### R2
- 需求ID: ADS-REQ-1.1
- 需求名称: 车辆控制
- 需求描述: 自动驾驶系统应该支持车辆控制。

#### R11
- 需求ID: ADS-REQ-1.1.1
- 需求名称: 加速控制
- 需求描述: 自动驾驶系统应该支持自动控制加速。

#### R12
- 需求ID: ADS-REQ-1.1.2
- 需求名称: 制动控制
- 需求描述: 自动驾驶系统应该支持自动控制制动。

#### R13
- 需求ID: ADS-REQ-1.1.3
- 需求名称: 方向控制
- 需求描述: 自动驾驶系统应该支持自动控制方向，包括转弯、变道和车道保持等。

#### R14
- 需求ID: ADS-REQ-1.1.4
- 需求名称: 停车和泊车功能
- 需求描述: 自动驾驶系统应该支持自动停车和泊车。

### R3
- 需求ID: ADS-REQ-1.2
- 需求名称: 感知与感知融合
- 需求描述: 自动驾驶系统应该支持感知和感知数据融合。

#### R15
- 需求名称: 道路感知与障碍检测
- 需求ID: ADS-REQ-1.2.1
- 需求描述: 自动驾驶系统应该支持使用传感器（如摄像头、激光雷达、雷达、超声波传感器）来检测道路上的障碍物、车辆、行人和交通信号。

#### R16
- 需求ID: ADS-REQ-1.2.2
- 需求名称: 传感器数据融合
- 需求描述: 自动驾驶系统应该整合不同传感器的数据以提高环境感知能力。

### R4
- 需求ID: ADS-REQ-1.3
- 需求名称: 高清地图和定位
- 需求描述: 自动驾驶系统应该支持高清地图和定位。

#### R9
- 需求ID: ADS-REQ-1.3.1
- 需求名称: 定位
- 需求描述: 自动驾驶系统应该使用高精度地图数据来辅助自车定位。

#### R10
- 需求ID: ADS-REQ-1.3.2
- 需求名称: 地图实时更新
- 需求描述: 自动驾驶系统应该实时更新和匹配地图。

### R5
- 需求ID: ADS-REQ-1.4
- 需求名称: 路径规划
- 需求描述: 自动驾驶系统应该根据不同场景做出相应的车辆的行进路径规划。

#### R17
- 需求名称: 障碍物识别和避免
- 需求描述: 自动驾驶系统应该识别路径上的障碍物，如其他车辆、行人、动物或静态障碍物，并规划绕过它们的路径。
- 需求ID: ADS-REQ-1.4.1
- 依赖 -> R15

#### R18
- 需求描述: 自动驾驶系统应该能够根据实时交通情况和障碍物的变化，动态更新行车路径，以保持路径的有效性和安全性。
- 需求名称: 动态更新行车路径
- 需求ID: ADS-REQ-1.4.2

#### R19
- 需求名称: 交通规则遵守
- 需求ID: ADS-REQ-1.4.3
- 需求描述: 自动驾驶系统应该遵守交通规则，包括遵守交通信号、限速等规定，以确保行车安全和法律遵从。

#### R20
- 需求ID: ADS-REQ-1.4.4
- 需求名称: 行车效率优化
- 需求描述: 自动驾驶系统应该根据当前交通情况、道路条件和目的地等因素，规划最优的行车路径，以实现行车效率的最大化

### R6
- 需求ID: ADS-REQ-1.5
- 需求名称: 决策和控制
- 需求描述: 自动驾驶系统应该支持基于感知数据和路径规划做出决策。
- 依赖 -> R5
- 依赖 -> R3

### R7
- 需求ID: ADS-REQ-1.6
- 需求名称: 通信
- 需求描述: 自动驾驶系统应该支持与其他车辆和交通基础设施进行通信。

#### R21
- 需求描述: 自动驾驶系统应该能够与周围其他车辆进行通信，以共享位置、速度、行驶方向等信息，帮助进行协同行驶和避免碰撞。
- 需求名称: 车辆对车辆通信（V2V）
- 需求ID: ADS-REQ-1.6.1

#### R22
- 需求描述: 自动驾驶系统应该能够与交通基础设施（如交通信号灯、路边传感器等）进行通信，获取实时的交通信息，比如交通流量、交通信号状态等，以优化行车路径和提高行车效率。
- 需求名称: 车辆对基础设施通信（V2I）
- 需求ID: ADS-REQ-1.6.2

#### R23
- 需求名称: 交通管理中心通信（V2C）
- 需求描述: 自动驾驶系统应该能够与交通管理中心进行通信，获取更全面的交通信息，如道路封闭、事故警报等，以及接收交通管理中心发出的指令，比如路线建议、交通管制等。
- 需求ID: ADS-REQ-1.6.3

#### R24
- 需求描述: 自动驾驶系统应该支持与其他车辆和交通基础设施之间使用的通信协议兼容，确保信息交换的顺畅和高效。
- 需求名称: 通信协议兼容性
- 需求ID: ADS-REQ-1.6.4

### R8
- 需求ID: ADS-REQ-1.7
- 需求名称: 安全性和紧急情况处理
- 需求描述: 自动驾驶系统应该支持自动应对紧急情况。

#### R25
- 需求ID: ADS-REQ-1.7.1
- 需求名称: 紧急情况处理
- 需求描述: 当检测到前方有障碍物或危险情况时,自动驾驶系统应该自动启动刹车以避免碰撞，并启动车辆的安全保护装置，例如气囊、预紧安全带等，以最大程度地保护乘客的安全。

#### R26
- 需求ID: ADS-REQ-1.7.2
- 需求描述: 当遇到紧急情况时,自动驾驶系统应该及时地向乘客下发安全通知，以便他们采取适当的措施。
- 需求名称: 安全通知下发

#### R27
- 需求名称: 紧急情况信息记录
- 需求ID: ADS-REQ-1.7.3
- 需求描述: 当遇到紧急情况时,自动驾驶系统应该自动记录发生紧急情况的相关信息，以便事后进行分析和改进系统的性能。
