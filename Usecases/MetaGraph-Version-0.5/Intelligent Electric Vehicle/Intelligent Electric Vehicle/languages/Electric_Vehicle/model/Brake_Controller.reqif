# Specification: Specification Document
- 名称: 制动系统

## REQ-1
- 名称: 驾驶制动
- 描述: 驾驶员应能够请求制动。

### REQ-1.1
- 描述: 驾驶员制动请求到实际开始减速的时间不应大于300ms。
- 名称: 响应时间
- Relation Type -> REQ-1

### REQ-1.2
- 描述: 停止时间应遵循欧盟制动系统指令的建议，3倍（制动距离）对于结冰是可以接受的。
- 名称: 制动距离
- Relation Type -> REQ-1

## REQ-2
- 描述: 该系统应为防抱死制动系统(ABS)，可防止车轮在制动时抱死。
- 名称: 防抱死制动

## REQ-3
- 描述: 操作员应能够使用制动踏板改变所需的制动力。完全踩下踏板意味着最大的制动力。
- 名称: 制动力

### REQ-3.1
- 描述: 未踩下制动踏板时，制动不得激活。
- 名称: 驾驶情况1
- Relation Type -> REQ-3

### REQ-3.2
- 描述: 如果踩下制动踏板且车轮速度大于零，则相应的ABS组件施加在车轮上的制动扭矩值最终应大于0。
- 名称: 驾驶情况2
- Relation Type -> REQ-3

### REQ-3.3
- 描述: 如果踩下制动踏板，车辆的实际速度大于10km/h，并且有一个车轮打滑，则该车轮对应的制动扭矩为零。
- 名称: 驾驶情况3
- Relation Type -> REQ-3
