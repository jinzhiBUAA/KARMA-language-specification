# Specification
- 名称: 智能驾驶系统

## REQ-1
- 名称: 感知层
- 描述: 数据采集层，主要由影响驾驶的各要素信息构成，即人、车、路的信息采集及三者信息的相互联系与交叉影响

### REQ-1.1
- 名称: 路况信息的采集
- 描述: 如道路几何构造，路面状况，道路灾害，路网条件及交通状况等，一般可通过GPS或北斗系统等高精度导航系统进行采集
- Relation -> REQ-1

### REQ-1.2
- 名称: 车辆信息
- 描述: 车辆信息主要包括车辆原始数据，如（车辆型号，车辆理论参数等）以及车辆行驶动态数据，如（行车速度，行车时间、行车轨迹等），一般可通过CAN总线的方式进行数据采集。
- Relation -> REQ-1

## REQ-2
- 名称: 网络层
- 描述: 数据的传输调度层，路况信息在经过导航系统进行数据采集后通过报文通信的方式进行数据传输，车辆信息有CAN总线进行数据采集后以GPRS通信模块的方式进行数据传输，数据传输至本层后，由本层进行汇总整合后传输至分析层中。

## REQ-3
- 名称: 分析层
- 描述: 数据的分析处理层，由于大数据采集与处理的无序性，在已定义的函数模型下，对影响驾驶的数据进行计算处理。处理结果将传送至应用层中，同时将返回至网络层中进行存储与调用，并在网络层中建立行驶数据库。

## REQ-4
- 名称: 应用层
- 描述: 应用服务层，依据数据采集与处理的结果，通过数据接口的方式可进行跨应用，跨系统之间的信息共享与信息协调。在互联网的大数据应用思维及互联互通的理念下，智能驾驶系统的应用主要为分为三大模块：用户服务系统、交通管理系统、汽车营销系统。

### REQ-4.1
- 名称: 用户服务系统
- 描述: 基于互联网思维的智能驾驶系统以驾驶员的行车安全性、舒适度等为约束，通过互联网的云处理与计算平台，得出建议的车辆安全行驶评定值、预警意见、适宜车速等驾驶控制数据流，由车体通过CAN总线接收数据，自动进行数据信号转换，进行行驶控制与调节，同时提出行驶对策的辅助指导可视化界面，人机交互协调车辆关系，保障行车安全，提高人的驾驶愉悦性。
- Relation -> REQ-4

### REQ-4.2
- 名称: 交通管理系统
- 描述: 通过对行驶数据库的调用，交通管理部门可准确、实时地掌握的行驶状况，更好地组织、规划、协调、指挥运输活动，提高道路行驶效率，降低交通损耗率。
- Relation -> REQ-4

### REQ-4.3
- 名称: 汽车营销系统
- 描述: 行驶数据库可为汽车企业提供企业数据服务，提高车体质量，促进企业方向性的发展。
- Relation -> REQ-4
