# 0_利益相关者列表
创建者：26453

# Specification: 需求表单文档
- 描述: 需求表单

## R1
- IOS: NASA
- 与系统关联: 探索计划规划者
- 提供能力: 指导火星探索计划、为火星探索活动一切支持

## R2
- IOS: 美国政府
- 与系统关联: 探索计划规划者
- 提供能力: 探索计划总体规划与经济支持

## R3
- IOS: JPL实验室
- 与系统关联: 地面支持者
- 提供能力: 服务火星车的探索过程

## R4
- IOS: 科学研究团队
- 与系统关联: 地面支持者
- 提供能力: 分析采集数据，服务探索过程

## R5
- IOS: 肯尼迪航天中心
- 与系统关联: 地面支持者
- 提供能力: 提供火星车测试、保证火箭发射

## R6
- IOS: 空气动力实验室
- 与系统关联: 地面支持者
- 提供能力: 控制调整火星车在太空和登陆是时的运行

## R8
- IOS: 毅力号
- 与系统关联: 主要运行系统
- 提供能力: 执行火星探测活动

## R7
- IOS: 运载火箭
- 与系统关联: 服务运行系统
- 提供能力: 运送火星车至太空

## R9
- IOS: 火星2020航天器
- 与系统关联: 服务运行系统
- 提供能力: 运送火星车至火星

## R10
- IOS: 地形相对导航系统
- 与系统关联: 功能运行系统
- 提供能力: 火星地表导航

## R11
- IOS: 火星勘测轨道飞行器
- 与系统关联: 功能运行系统
- 提供能力: 火星轨道监测

## R12
- IOS: 雷达和摄像系统
- 与系统关联: 功能运行系统
- 提供能力: 导航、拍照、分析

## R13
- IOS: Ingenuity直升机
- 与系统关联: 功能运行系统
- 提供能力: 无人机实验与探索

## R14
- IOS: 环境矿物扫描分析仪
- 与系统关联: 功能运行系统
- 提供能力: 地质、环境、生命探索

## R15
- IOS: 地形传感器
- 与系统关联: 功能运行系统
- 提供能力: 地质探索、导航

## R16
- IOS: 岩石化学扫描仪
- 与系统关联: 功能运行系统
- 提供能力: 样本分析

## R17
- IOS: 钻孔取芯机构
- 与系统关联: 功能运行系统
- 提供能力: 样本采集

## R18
- IOS: 录音设备
- 与系统关联: 功能运行系统
- 提供能力: 声音样本采集
