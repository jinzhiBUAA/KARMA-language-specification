# 0_4_3_使命阶段能力分析
创建者：26453

# Specification: 需求表单文档
- 描述: 需求表单

## R1 (需求类型)
- 阶段名称: 火星车制造阶段

### R4 (需求类型)
- 能力需求: 火星车设计
- 预期效果: 符合探索计划要求
- 阶段名称: 提出火星车制造方案

### R5 (需求类型)
- 能力需求: 火星车生产
- 预期效果: 符合探索计划要求
- 阶段名称: 制造火星车

### R6 (需求类型)
- 能力需求: 火星车测试
- 预期效果: 能够适应太空与火星工作环境
- 阶段名称: 测试火星车

## R3 (需求类型)
- 阶段名称: 火星车发射阶段

### R7 (需求类型)
- 阶段名称: 运载火箭发射
- 能力需求: 火箭搭载升空
- 预期效果: 借助运载火箭安全进入太空

### R8 (需求类型)
- 阶段名称: 巡航靠近火星
- 能力需求: 太空推进能力
- 预期效果: 借助航天器前往火星，在太空中维持正常运转

### R9 (需求类型)
- 阶段名称: 进入火星大气层
- 能力需求: 太空推进能力
- 预期效果: 借助航天器进入火星轨道，突破大气层

### R10 (需求类型)
- 阶段名称: 调整降落姿态
- 能力需求: 推进能力

#### R26 (需求类型)
- 能力需求: 姿态感知能力
- 预期效果: 矫正降落姿态保护设备

### R11 (需求类型)
- 阶段名称: 打开降落伞缓冲落地
- 能力需求: 高度感知能力
- 预期效果: 在正确高度打开降落伞进行落地前缓冲减速

### R12 (需求类型)
- 阶段名称: 记录着陆过程数据
- 能力需求: 数据采集能力
- 预期效果: 采集降落过程中高度变化以及声音、气象数据

### R13 (需求类型)
- 阶段名称: 落地设备检查
- 能力需求: 自检实验能力
- 预期效果: 确认降落时毅力号能够正常运行

## R14 (需求类型)
- 阶段名称: 区域探索阶段

### R15 (需求类型)
- 阶段名称: 确定定位与行进路线
- 能力需求: 定位导航能力
- 预期效果: 确定降落精确位置，并按计划路线自主导航前行

### R16 (需求类型)
- 阶段名称: 前往探索区域
- 能力需求: 定位导航能力
- 预期效果: 正确到达预期探索地点

### R17 (需求类型)
- 阶段名称: 目标区域地表分析
- 能力需求: 实验分析能力

#### R28 (需求类型)
- 能力需求: 数据分析能力
- 预期效果: 完成区域地质探索

### R18 (需求类型)
- 阶段名称: 生命迹象分析
- 能力需求: 实验分析能力
- 预期效果: 完成区域生命迹象分析

### R19 (需求类型)
- 阶段名称: 采集样本保存
- 能力需求: 取样能力
- 预期效果: 采集实验样本，并携带储存

### R20 (需求类型)
- 阶段名称: 照片、气象数据采集
- 能力需求: 数据采集能力
- 预期效果: 对探索区域完成气象、照片、地质数据采集

### R21 (需求类型)
- 阶段名称: 无人机测试
- 能力需求: 自主控制能力
- 预期效果: 自动控制无人机进行火星表面空中飞行试验

## R22 (需求类型)
- 阶段名称: 实验阶段

### R23 (需求类型)
- 阶段名称: 无人机飞行探索测试
- 能力需求: 自主控制能力
- 预期效果: 自动控制无人机进行火星表面空中飞行试验

### R24 (需求类型)
- 阶段名称: 进行制氧测试
- 能力需求: 自主控制能力
- 预期效果: 自动控制制氧仪器工作完成实验，并将数据传回地面

### R25 (需求类型)
- 阶段名称: 样本储存标记
- 能力需求: 自主控制能力
- 预期效果: 自动控制选定地点保存样本，并将数据传回地面

## R2

## R27 (需求类型)
- 能力需求: 通信能力
