# 2_7_1系统需求识别
创建者：26453

# Specification: 需求表单文档
- 描述: 需求表单

## R1
- 描述: 从这里开始编辑。
- 系统需求: 运载火箭安全发射

## R2
- 系统需求: 与地面正常交流

## R3
- 系统需求: 自主控制

## R4
- 系统需求: 太空巡航能力

## R5
- 系统需求: 探索分析能力

## R6
- 系统需求: 样本采集能力

## R7
- 系统需求: 信息采集能力
