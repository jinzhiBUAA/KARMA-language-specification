# 1_4_1_运行-使命-兴趣系统对应关系
创建者：26453

# Specification: 需求表单文档
- 描述: 需求表单

## R1
- 描述: 从这里开始编辑。
- 使命阶段: 火星车制造阶段
- 运行阶段: 发射前阶段
- 兴趣系统生命周期阶段: 毅力号的设计制造

## R2
- 使命阶段: 火星车发射阶段
- 运行阶段: 发射阶段
- 兴趣系统生命周期阶段: 毅力号的发射前往火星

### R7
- 运行阶段: 登陆阶段
- 兴趣系统生命周期阶段: 毅力号降落阶段

## R3
- 使命阶段: 火星车探索阶段1（Jezero区域）
- 运行阶段: 火星探索阶段
- 兴趣系统生命周期阶段: 毅力号探索阶段

## R4
- 使命阶段: 火星车探索阶段2（Paver Stones区域）
- 运行阶段: 火星探索阶段
- 兴趣系统生命周期阶段: 毅力号探索阶段

## R5
- 使命阶段: 火星车探索阶段3（Three Forks区域）
- 运行阶段: 火星探索阶段
- 兴趣系统生命周期阶段: 毅力号探索阶段

## R6
- 使命阶段: 火星车探索阶段4（实验测试阶段）
- 运行阶段: 火星探索阶段
- 兴趣系统生命周期阶段: 毅力号探索阶段
